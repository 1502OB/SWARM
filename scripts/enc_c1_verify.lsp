;; Independent read-only check of N_P_REV5 clouds/tags on P1.00 and P1.01 (orchestrator, not the scripter's CHECK).
(defun c:ENC-C1-V ( / r ss i e ed nc nt bad att pts bs a j p1 p2 a2 ad)
  (setq r "")
  (foreach L '("P1.00" "P1.01")
    (setq ss (ssget "_X" (list '(8 . "N_P_REV5") (cons 410 L))) i 0 nc 0 nt 0 bad 0 att "")
    (if ss
      (while (< i (sslength ss))
        (setq e (ssname ss i) ed (entget e))
        (cond
          ((= (cdr (assoc 0 ed)) "LWPOLYLINE")
           (setq nc (1+ nc) pts nil bs nil a 0.0)
           (foreach g ed
             (if (= (car g) 10) (setq pts (cons (cdr g) pts)))
             (if (= (car g) 42) (setq bs (cons (cdr g) bs))))
           (setq pts (reverse pts) j 0)
           (while (< j (length pts))
             (setq p1 (nth j pts) p2 (nth (rem (1+ j) (length pts)) pts)
                   a (+ a (- (* (car p1) (cadr p2)) (* (car p2) (cadr p1)))) j (1+ j)))
           (if (or (/= 1 (logand 1 (cdr (assoc 70 ed)))) (<= a 0)
                   (> (abs (- (apply 'min bs) 0.520567)) 1e-4)
                   (> (abs (- (apply 'max bs) 0.520567)) 1e-4)
                   (/= 1 (cdr (assoc 67 ed))))
             (setq bad (1+ bad))))
          ((= (cdr (assoc 0 ed)) "INSERT")
           (setq nt (1+ nt) a2 (entnext e))
           (while (and a2 (= (cdr (assoc 0 (setq ad (entget a2)))) "ATTRIB"))
             (setq att (strcat att (cdr (assoc 2 ad)) "=" (cdr (assoc 1 ad)) " ") a2 (entnext a2)))))
        (setq i (1+ i))))
    (setq r (strcat r L ": clouds=" (itoa nc) " bad=" (itoa bad) " tags=" (itoa nt) " attrs=" att "| ")))
  r)
