;; ENC-C2.lsp - replace the delta-5 clouds on P1.00/P1.01 with tight clouds from ENC-C2.rects.txt.
;; (c:ENC-C2-RUN): deletes every entity on N_P_REV5 on P1.00/P1.01 (the ENC-C1 clouds + tags; collect-then-delete),
;; then for each rect draws a closed CCW cloud (chord ~0.10, bulge +0.520567, layer N_P_REV5, paper space) and a
;; DELTA-TAG (A=5) whose triangle's lower-left vertex touches the cloud's top-right corner. One undo group.
;; Writes created handles to ENC-C2.created.txt. (c:ENC-C2-CHECK) verifies.
(vl-load-com)
(setq C2:B 0.520567 C2:CH 0.10 C2:DX 0.166029 C2:DY 0.095857)
(defun _c2-split (s d / r p)
  (while (setq p (vl-string-search d s)) (setq r (cons (substr s 1 p) r) s (substr s (+ p 2))))
  (reverse (cons s r)))
(defun _c2-side (x0 y0 x1 y1 / L n i r)
  (setq L (distance (list x0 y0) (list x1 y1)) n (max 1 (fix (+ 0.5 (/ L C2:CH)))) i 0)
  (while (< i n) (setq r (cons (list (+ x0 (* (- x1 x0) (/ (float i) n))) (+ y0 (* (- y1 y0) (/ (float i) n)))) r) i (1+ i)))
  (reverse r))
(defun _c2-cloud (blk x0 y0 x1 y1 / pts arr pl k)
  (setq pts (append (_c2-side x0 y0 x1 y0) (_c2-side x1 y0 x1 y1) (_c2-side x1 y1 x0 y1) (_c2-side x0 y1 x0 y0)))
  (setq arr (vlax-make-safearray vlax-vbDouble (cons 0 (1- (* 2 (length pts))))))
  (vlax-safearray-fill arr (apply 'append pts))
  (setq pl (vla-AddLightWeightPolyline blk arr))
  (vla-put-Closed pl :vlax-true) (vla-put-Layer pl "N_P_REV5")
  (setq k 0) (repeat (length pts) (vla-SetBulge pl k C2:B) (setq k (1+ k)))
  pl)
(defun _c2-tag (blk x1 y1 / ins a)
  (setq ins (vla-InsertBlock blk (vlax-3d-point (+ x1 C2:DX) (+ y1 C2:DY) 0.0) "DELTA-TAG" 1.0 1.0 1.0 0.0))
  (vla-put-Layer ins "N_P_REV5")
  (foreach a (vlax-invoke ins 'GetAttributes) (if (= (strcase (vla-get-TagString a)) "A") (vla-put-TextString a "5")))
  ins)
(defun _c2-blk (L) (vla-get-Block (vla-Item (vla-get-Layouts (vla-get-ActiveDocument (vlax-get-acad-object))) L)))
(defun c:ENC-C2-RUN ( / doc f line p rects old ss i made blk o fo n)
  (setq doc (vla-get-ActiveDocument (vlax-get-acad-object)))
  (if (not (tblsearch "BLOCK" "DELTA-TAG")) (exit))
  (setq f (open "C:/Users/Jeremy/swarm/manifests/ENC-C2.rects.txt" "r"))
  (while (setq line (read-line f)) (if (> (strlen line) 5) (setq rects (cons (_c2-split line "|") rects))))
  (close f)
  (foreach L '("P1.00" "P1.01")
    (setq ss (ssget "_X" (list '(8 . "N_P_REV5") (cons 410 L))) i 0)
    (if ss (while (< i (sslength ss)) (setq old (cons (ssname ss i) old) i (1+ i)))))
  (vla-StartUndoMark doc)
  (foreach e old (vla-Delete (vlax-ename->vla-object e)))
  (foreach r (reverse rects)
    (setq blk (_c2-blk (nth 0 r)))
    (setq o (_c2-cloud blk (atof (nth 1 r)) (atof (nth 2 r)) (atof (nth 3 r)) (atof (nth 4 r))))
    (setq made (cons (vla-get-Handle o) made))
    (setq o (_c2-tag blk (atof (nth 3 r)) (atof (nth 4 r))))
    (setq made (cons (vla-get-Handle o) made)))
  (vla-EndUndoMark doc)
  (setq fo (open "C:/Users/Jeremy/swarm/manifests/ENC-C2.created.txt" "w"))
  (foreach h (reverse made) (write-line h fo)) (close fo)
  (strcat "deleted=" (itoa (length old)) " clouds=" (itoa (length rects)) " tags=" (itoa (length rects))))
(defun c:ENC-C2-CHECK ( / r L ss i ed nc nt bad pts bs a j p1 p2)
  (setq r "")
  (foreach L '("P1.00" "P1.01")
    (setq ss (ssget "_X" (list '(8 . "N_P_REV5") (cons 410 L))) i 0 nc 0 nt 0 bad 0)
    (if ss (while (< i (sslength ss))
      (setq ed (entget (ssname ss i)))
      (cond ((= (cdr (assoc 0 ed)) "LWPOLYLINE")
             (setq nc (1+ nc) pts nil bs nil a 0.0)
             (foreach g ed (if (= (car g) 10) (setq pts (cons (cdr g) pts))) (if (= (car g) 42) (setq bs (cons (cdr g) bs))))
             (setq pts (reverse pts) j 0)
             (while (< j (length pts)) (setq p1 (nth j pts) p2 (nth (rem (1+ j) (length pts)) pts) a (+ a (- (* (car p1) (cadr p2)) (* (car p2) (cadr p1)))) j (1+ j)))
             (if (or (/= 1 (logand 1 (cdr (assoc 70 ed)))) (<= a 0) (> (abs (- (apply 'min bs) C2:B)) 1e-4) (> (abs (- (apply 'max bs) C2:B)) 1e-4)) (setq bad (1+ bad))))
            ((= (cdr (assoc 0 ed)) "INSERT") (setq nt (1+ nt))))
      (setq i (1+ i))))
    (setq r (strcat r L ": clouds=" (itoa nc) " tags=" (itoa nt) " bad=" (itoa bad) " | ")))
  r)
