;;; test_swarm_lib.lsp - tests for swarm_lib.lsp, run headless on a scratch drawing copy:
;;;   (from the swarm root, i.e. SWARM_HOME or %USERPROFILE%/swarm)
;;;   python tools/lsp_dryrun.py library/acad/test_swarm_lib.lsp <scratch copy of any sheet .dwg> SWLTEST --run
;;; The drawing should have a paper layout with a floating viewport (e.g. a copy of a backups/<run>/P1.03 sheet) so the
;;; floating-vps / on-sheet-p checks test real viewports; never point it at an L: original (the tool copies it anyway).
;;; PLAN = pure-LISP tests; RUN = tests that entmake test geometry far from the drawing (x=1e6) on the copy only.
;;; Each returns "pass=<n> fail=<n> | <failed names>". ActiveX-only helpers ([AX]) are not tested here.

(defun swlt:check (name ok)
  (if ok (setq SWLT:PASS (1+ SWLT:PASS)) (setq SWLT:FAIL (1+ SWLT:FAIL) SWLT:BAD (cons name SWLT:BAD)))
  ok)
(defun swlt:report ()
  (strcat "pass=" (itoa SWLT:PASS) " fail=" (itoa SWLT:FAIL)
          (if SWLT:BAD (strcat " | failed: " (swl:join (reverse SWLT:BAD) ",")) "")))

(defun c:SWLTEST-PLAN (/ vp b d ed)
  (setq SWLT:PASS 0 SWLT:FAIL 0 SWLT:BAD nil)
  (swlt:check "join" (= (swl:join (list "a" "b" "c") ",") "a,b,c"))
  (swlt:check "join-empty" (= (swl:join nil ",") ""))
  (swlt:check "san-newline" (= (swl:san (strcat "a" (chr 10) "b" (chr 13) (chr 9) "\"q\"")) "a | b 'q'"))
  (swlt:check "result" (= (swl:result 2 1 0 (list "1A" "1B") "ok") "done=2 skipped=1 failed=0 | ids=1A,1B | ok"))
  (swlt:check "result-one-line" (not (vl-string-search (chr 10) (swl:result 1 0 0 nil (strcat "x" (chr 10) "y")))))
  (swlt:check "norm" (equal (swl:norm (list 5 1) (list 2 4)) (list 2 1 5 4)))
  (swlt:check "pad" (equal (swl:pad (list 0 0 1 1) 0.5) (list -0.5 -0.5 1.5 1.5)))
  (swlt:check "union" (equal (swl:union (list 0 0 1 1) (list 2 -1 3 0)) (list 0 -1 3 1)))
  (swlt:check "inbox" (and (swl:inbox (list 1 1) (list 0 0 2 2)) (not (swl:inbox (list 3 1) (list 0 0 2 2)))))
  (swlt:check "ovl" (and (swl:ovl (list 0 0 2 2) (list 1 1 3 3)) (not (swl:ovl (list 0 0 1 1) (list 1 1 2 2)))))
  (swlt:check "close" (and (swl:close 1.0 1.004 0.005) (not (swl:close 1.0 1.01 0.005))))
  (swlt:check "uniq" (equal (swl:uniq (list "a" "b" "a" "c" "b")) (list "a" "b" "c")))
  (swlt:check "seghit-inside" (swl:seghit (list 1 1) (list 5 5) (list 0 0 2 2)))
  (swlt:check "seghit-crossing" (swl:seghit (list -1 1) (list 3 1) (list 0 0 2 2)))
  (swlt:check "seghit-miss" (not (swl:seghit (list -1 3) (list 3 3) (list 0 0 2 2))))
  (swlt:check "vtxbox" (equal (swl:vtxbox (list (cons 10 (list 1 2)) (cons 10 (list 4 -1)))) (list 1 -1 4 2)))
  (setq b (list 0.0 0.0 1.0 0.5))
  (swlt:check "cloudpts-count" (= (length (swl:cloudpts b 0.25)) 12))
  (swlt:check "cloudpts-first-BL" (equal (car (swl:cloudpts b 0.25)) (list 0.0 0.0)))
  ;; synthetic viewport: paper centre (10,10), view centre (100,200), target 0, scale k = 0.5
  (setq vp (list (list 10.0 10.0) (list 0.0 0.0 0.0) (list 100.0 200.0) 0.5 (list 5.0 5.0 15.0 15.0)))
  (swlt:check "ms->ps" (equal (swl:ms->ps vp (list 110.0 210.0)) (list 15.0 15.0) 1e-9))
  (swlt:check "ps->ms" (equal (swl:ps->ms vp (list 15.0 15.0)) (list 110.0 210.0) 1e-9))
  (swlt:check "roundtrip" (equal (swl:ps->ms vp (swl:ms->ps vp (list 97.3 188.1))) (list 97.3 188.1) 1e-9))
  (swlt:check "box->ms" (equal (swl:box->ms vp (list 5.0 5.0 15.0 15.0)) (list 90.0 190.0 110.0 210.0) 1e-9))
  (swlt:check "inside-vp" (and (swl:inside-vp vp (list 6 6 8 8)) (not (swl:inside-vp vp (list 6 6 16 8)))))
  (swlt:check "best-spot-first-clear"
    (equal (car (swl:best-spot (list (list 0 0 1 1) (list 5 5 6 6)) (function (lambda (bx) (if (= (car bx) 0) (list "h1") nil)))))
           (list 5 5 6 6)))
  (swlt:check "queue-refuses-erase" (wcmatch (swl:queue-command "_.ERASE ALL ") "ABORT*"))
  (swlt:check "words" (equal (swl:words "_.-XREF A file.dwg") (list "_.-XREF" "A" "file.dwg")))
  ;; 2026-11-09 helpers (A32-A50)
  (setq d (swl:swarm-dir))
  (swlt:check "swarm-dir-slashes" (and (= (substr d (strlen d)) "/") (not (vl-string-search "\\" d))))
  (swlt:check "swarm-dir-default" (or (getenv "SWARM_HOME")
                                      (= (strcase d) (strcase (strcat (vl-string-translate "\\" "/" (getenv "USERPROFILE")) "/swarm/")))))
  ;; A34 rule: top 20, bbox height 2 but DXF 43 = 5 -> bottom 15; bbox taller than 43 -> bbox bottom; negative 43 ignored
  (swlt:check "mtext-rule-43" (equal (swl:mtext-rule (list 0.0 18.0 5.0 20.0) 5.0) (list 0.0 15.0 5.0 20.0) 1e-9))
  (swlt:check "mtext-rule-bbox" (equal (swl:mtext-rule (list 0.0 10.0 5.0 20.0) 3.0) (list 0.0 10.0 5.0 20.0) 1e-9))
  (swlt:check "mtext-rule-neg43" (equal (swl:mtext-rule (list 0.0 10.0 5.0 20.0) -2775.0) (list 0.0 10.0 5.0 20.0) 1e-9))
  ;; A33: vp paper box (5 5 15 15); a box 0.04 outside fails plain, passes with the default 0.10 tolerance
  (swlt:check "inside-vp-tol-default" (and (not (swl:inside-vp vp (list 4.96 6 8 8))) (swl:inside-vp-tol vp (list 4.96 6 8 8) nil)))
  (swlt:check "inside-vp-tol-too-far" (not (swl:inside-vp-tol vp (list 4.5 6 8 8) nil)))
  (swlt:check "inside-vp-tol-explicit" (and (swl:inside-vp-tol vp (list 4.5 6 8 8) 0.6) (not (swl:inside-vp-tol vp (list 4.5 6 8 8) 0.4))))
  (swlt:check "inside-vp-tol-tiny-box" (swl:inside-vp-tol vp (list 14.95 6 15.05 6.1) nil))
  (setq ed (list (cons 0 "VIEWPORT") (list 10 10.0 10.0 0.0) (list 12 100.0 200.0 0.0) (list 17 0.0 0.0 0.0)
                 (cons 40 10.0) (cons 41 5.0) (cons 45 10.0)))
  (swlt:check "vp-msbox" (equal (swl:vp-msbox ed) (list 90.0 195.0 110.0 205.0) 1e-9))
  (swlt:check "vp-msbox-twist-90" (equal (swl:vp-msbox (append ed (list (cons 51 (/ pi 2.0))))) (list 95.0 190.0 105.0 210.0) 1e-9))
  (swlt:report))

(defun c:SWLTEST-RUN (/ x0 l1 l2 t1 h1 c ed ck hits m1 m2 h43 mb l3 gb lf l4 l5 l6 hf h4 fn rs f ln ln2 lo fv vb cx cy vr)
  (setq SWLT:PASS 0 SWLT:FAIL 0 SWLT:BAD nil x0 1000000.0)
  ;; two lines: one crossing the test box, one far away; a text with known values
  (setq l1 (progn (entmake (list '(0 . "LINE") '(410 . "Model") '(8 . "0") (list 10 (- x0 5) 1.0 0.0) (list 11 (+ x0 5) 1.0 0.0))) (entlast)))
  (setq l2 (progn (entmake (list '(0 . "LINE") '(410 . "Model") '(8 . "0") (list 10 (+ x0 100) 50.0 0.0) (list 11 (+ x0 101) 51.0 0.0))) (entlast)))
  (setq t1 (progn (entmake (list '(0 . "TEXT") '(410 . "Model") '(8 . "0") (list 10 x0 20.0 0.0) '(40 . 2.5) '(1 . "ZURN 375AST"))) (entlast)))
  (setq h1 (cdr (assoc 5 (entget t1))))
  (setq hits (swl:clash "Model" (list (- x0 1) 0.0 (+ x0 1) 2.0) nil 0.0 2000))
  (swlt:check "clash-crossing-line" (member (cdr (assoc 5 (entget l1))) hits))
  (swlt:check "clash-ignores-far-line" (not (member (cdr (assoc 5 (entget l2))) hits)))
  (swlt:check "clash-skip" (not (member (cdr (assoc 5 (entget l1)))
                                        (swl:clash "Model" (list (- x0 1) 0.0 (+ x0 1) 2.0) (list (cdr (assoc 5 (entget l1)))) 0.0 2000))))
  (swlt:check "preflight-ok" (null (swl:preflight (list (list h1 1 "ZURN 375AST" nil) (list h1 40 2.5 1e-9)
                                                        (list h1 10 (list x0 20.0) 0.001)))))
  (swlt:check "preflight-text-changed" (wcmatch (swl:preflight (list (list h1 1 "OTHER" nil))) "*planned*"))
  (swlt:check "preflight-moved" (wcmatch (swl:preflight (list (list h1 10 (list x0 25.0) 0.001))) "*moved*"))
  (swlt:check "preflight-missing" (wcmatch (swl:preflight (list (list "FFFFFF" 1 "x" nil))) "*missing*"))
  (setq c (swl:entmake-cloud (swl:pad (list x0 30.0 (+ x0 2.0) 31.0) 0.1) 0.34 -0.52 "0" "Model"))
  (swlt:check "cloud-entmake" c)
  (if c (progn (setq ck (swl:cloud-check (entget c) -0.52))
               (swlt:check "cloud-clockwise-closed" (car ck))
               (swlt:check "cloud-vertex-box" (equal (cadr ck) (list (- x0 0.1) 29.9 (+ x0 2.1) 31.1) 1e-6))))
  (swlt:check "cloud-check-rejects-wrong-bulge" (if c (not (car (swl:cloud-check (entget c) 0.52))) nil))
  ;; ---- 2026-11-09 helpers (A32-A50)
  ;; MTEXT: top-left attachment at y=100 and bottom-left at y=50; bottom = top - max(bbox h, DXF 43)
  (setq m1 (progn (entmake (list '(0 . "MTEXT") '(100 . "AcDbEntity") '(410 . "Model") '(8 . "0") '(100 . "AcDbMText")
                                 (list 10 x0 100.0 0.0) '(40 . 2.0) '(41 . 50.0) '(71 . 1) '(1 . "SWLTEST NOTE")))
                  (entlast)))
  (setq m2 (progn (entmake (list '(0 . "MTEXT") '(100 . "AcDbEntity") '(410 . "Model") '(8 . "0") '(100 . "AcDbMText")
                                 (list 10 (+ x0 10.0) 50.0 0.0) '(40 . 2.0) '(41 . 50.0) '(71 . 7) '(1 . "SWLTEST NOTE")))
                  (entlast)))
  (setq h43 (swl:dxf0 43 (entget m1)) mb (swl:mtext-box m1))
  (swlt:check "mtext-h43-positive" (> h43 0.0))
  (swlt:check "mtext-bottom-top-attach" (equal (swl:mtext-bottom m1) (- 100.0 (max h43 (- (cadddr mb) (cadr mb)))) 1e-6))
  (swlt:check "mtext-bottom-top-attach-value" (equal (swl:mtext-bottom m1) (- 100.0 h43) 1e-6))
  (swlt:check "mtext-bottom-bottom-attach" (equal (swl:mtext-bottom m2) 50.0 1e-6))
  (swlt:check "mtext-bottom-by-handle" (equal (swl:mtext-bottom (cdr (assoc 5 (entget m1)))) (swl:mtext-bottom m1) 1e-9))
  (swlt:check "mtext-bottom-not-mtext" (null (swl:mtext-bottom l1)))
  ;; group box: line + mtext + bulged cloud; and nil if a member is missing
  (setq l3 (progn (entmake (list '(0 . "LINE") '(410 . "Model") '(8 . "0") (list 10 (- x0 3.0) 95.0 0.0) (list 11 (- x0 1.0) 97.0 0.0))) (entlast)))
  (setq gb (swl:group-box (list (cdr (assoc 5 (entget l3))) (cdr (assoc 5 (entget m1))))))
  (swlt:check "group-box-union" (and gb (equal gb (list (- x0 3.0) (min 95.0 (cadr mb)) (caddr mb) 100.0) 1e-6)))
  (swlt:check "group-box-missing-member" (null (swl:group-box (list (cdr (assoc 5 (entget l3))) "FFFFFF"))))
  (if c (swlt:check "ebox-cloud-covers-arcs"
          (and (setq gb (swl:ebox c)) (< (car gb) (- x0 0.1)) (> (cadddr gb) 31.1))))
  ;; clash-ex: a FRAME line and a layer-0 line both cross the box; FRAME is excluded, layer 0 still counts
  (setq lf (progn (entmake (list '(0 . "LINE") '(410 . "Model") '(8 . "FRAME") (list 10 (- x0 5) 61.0 0.0) (list 11 (+ x0 5) 61.0 0.0))) (entlast)))
  (setq l4 (progn (entmake (list '(0 . "LINE") '(410 . "Model") '(8 . "0") (list 10 x0 55.0 0.0) (list 11 x0 65.0 0.0))) (entlast)))
  (setq hf (cdr (assoc 5 (entget lf))) h4 (cdr (assoc 5 (entget l4))))
  (setq hits (swl:clash "Model" (list (- x0 1) 60.0 (+ x0 1) 62.0) nil 0.0 2000))
  (swlt:check "clash-sees-frame" (and (member hf hits) (member h4 hits)))
  (setq hits (swl:clash-ex "Model" (list (- x0 1) 60.0 (+ x0 1) 62.0) nil 0.0 2000 (list "frame")))
  (swlt:check "clash-ex-drops-frame" (and (not (member hf hits)) (member h4 hits)))
  ;; corner cut (no endpoint inside, spans neither the full width nor height) and a near miss beside the corner
  (setq l5 (progn (entmake (list '(0 . "LINE") '(410 . "Model") '(8 . "0") (list 10 (- x0 2.0) 61.0 0.0) (list 11 x0 63.0 0.0))) (entlast)))
  (setq l6 (progn (entmake (list '(0 . "LINE") '(410 . "Model") '(8 . "0") (list 10 (- x0 2.0) 61.5 0.0) (list 11 (- x0 0.5) 63.5 0.0))) (entlast)))
  (setq hits (swl:clash "Model" (list (- x0 1) 60.0 (+ x0 1) 62.0) nil 0.0 2000))
  (swlt:check "clash-corner-cut" (member (cdr (assoc 5 (entget l5))) hits))
  (swlt:check "clash-near-miss" (not (member (cdr (assoc 5 (entget l6))) hits)))
  (swlt:check "clash-ex-abort-shape" (equal (swl:clash-ex "Model" (list (- x0 1) 60.0 (+ x0 1) 62.0) nil 0.0 0 (list "FRAME"))
                                             (list "ABORT too-many")))
  ;; result-out: file written (one line) and the same string returned; the test file is deleted again
  (setq fn (strcat (swl:swarm-dir) "scripts/SWLTEST-RESULT.result.txt"))
  (setq rs (swl:result-out "SWLTEST-RESULT" (swl:result 1 0 0 (list "AB") (strcat "x" (chr 10) "y"))))
  (swlt:check "result-out-returns" (= rs "done=1 skipped=0 failed=0 | ids=AB | x | y"))
  (setq f (open fn "r") ln (if f (read-line f)) ln2 (if f (read-line f)))
  (if f (close f))
  (swlt:check "result-out-file" (and (= ln rs) (null ln2)))
  (swl:result-out "SWLTEST-RESULT" "second")
  (setq f (open fn "r") ln (if f (read-line f)))
  (if f (close f))
  (swlt:check "result-out-overwrites" (= ln "second"))
  (vl-file-delete fn)
  ;; floating viewports on the current layout (the copy's own viewports) and on-sheet-p through them
  (setq lo (getvar "CTAB") fv (if (/= (strcase lo) "MODEL") (swl:floating-vps lo)))
  (swlt:check "floating-vps-all-gt1" (vl-every (function (lambda (e) (> (cdr (assoc 69 (entget e))) 1))) fv))
  (swlt:check "floating-vps-model-none" (null (swl:floating-vps "Model")))
  (swlt:check "floating-vps-no-layout" (null (swl:floating-vps "NO SUCH LAYOUT")))
  (swlt:check "on-sheet-far-box" (not (swl:on-sheet-p (list 1.0e9 1.0e9 (+ 1.0e9 1.0) (+ 1.0e9 1.0)))))
  (if fv
    (progn
      (setq vb (swl:vp-msbox (entget (car fv))) cx (/ (+ (car vb) (caddr vb)) 2.0) cy (/ (+ (cadr vb) (cadddr vb)) 2.0))
      (swlt:check "on-sheet-vp-centre" (swl:on-sheet-p (list (- cx 0.5) (- cy 0.5) (+ cx 0.5) (+ cy 0.5))))
      ;; vp-msbox agrees with swl:vp / swl:box->ms (untwisted viewports): the paper box maps to the same model box
      (setq vr (swl:vp (cdr (assoc 5 (entget (car fv)))) lo))
      (swlt:check "vp-msbox-matches-box->ms" (or (= (type vr) 'STR) (equal (swl:box->ms vr (nth 4 vr)) vb 1e-6))))
    (swlt:check "on-sheet-needs-a-floating-viewport (use a sheet DWG)" nil))
  (strcat (swlt:report) " | layout=" lo " floating=" (itoa (length fv))))

(princ)
